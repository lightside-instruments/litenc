module tntapi-node-access-statistics {

  namespace
    "urn:tntapi:node-access-statistics";
  prefix "node-access-statistics";

  import "ietf-network" { prefix nd; }

  organization
    "tntapi project";

  contact
    "Vladimir Vassilev <mailto:vladimir@lightside-instruments.com>";

  description
    "Extends network nodes with connection and data operation statistics.";

  revision 2026-11-01 {
    description
      "Initial revision.";
  }

  augment "/nd:networks/nd:network/nd:node" {
    description
      "Adds operation durations for network nodes.";

    leaf connect-duration {
      type uint64;
      units "nanoseconds";
      description
        "Elapsed monotonic time spent establishing the connection to the node,
         including authentication and session setup.";
    }
    leaf write-duration {
      type uint64;
      units "nanoseconds";
      description
        "Elapsed monotonic time from sending a configuration write request
         to receiving its reply. Replaced on each configuration write.";
    }
    leaf commit-duration {
      type uint64;
      units "nanoseconds";
      description
        "Elapsed monotonic time from sending a commit request to receiving
         its reply, including time spent collecting earlier nodes' replies.
         Replaced on each commit.";
    }
    leaf read-duration {
      type uint64;
      units "nanoseconds";
      description
        "Elapsed monotonic time from sending a read request to receiving
         its reply, including time spent collecting earlier nodes' replies.
         Replaced on each read and absent for skipped nodes.";
    }
  }
}
